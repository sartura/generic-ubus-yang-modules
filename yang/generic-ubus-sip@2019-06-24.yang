module generic-ubus-sip {
    yang-version 1.1;
    namespace "https://terastream/ns/yang/generic-ubus-sip";
    prefix "gus";

    revision 2019-06-24 {
		description "Initial revision.";
	}


    container generic-ubus-sip {
        config false;
        container registry_status {
            list registry {
                key name;
                leaf name {
                    type string;
                }
                leaf username {
                    type string;
                }
                leaf refresh {
                    type uint32;
                }
                leaf state {
                    type string;
                }
                leaf  registered {
                    type boolean;
                }
            }
        }
    }
}
