module weather-report  {
	yang-version 1.1;
	namespace "https://generic-ubus/weather-report";
	prefix "ft";

	import ietf-yang-types {
		prefix "iyt";
	}

	revision "2019-06-13" {
		description "Initial revision.";
	}

	feature show-date-time;

	container weather-report {
		config false;

		container status {
			config false;
			leaf city {
				type string;
			}
			leaf temperature {
				type int32;
			}
			leaf date-time {
				if-feature show-date-time;
				type iyt:date-and-time;
			}
		}

	}
}
