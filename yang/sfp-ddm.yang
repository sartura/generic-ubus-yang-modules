module sfp-ddm {
    yang-version 1.1;
    namespace "https://terastream/ns/yang/sfp-ddm";
    prefix "sd";

    revision 2019-06-18 {
        description "Initial revision.";
    }

    container sfp-ddm {
        config false;
        container get-tx-pwr {
            leaf tx-pwr {
                type string;
            }
        }
        container get-rx-pwr {
            leaf rx-pwr {
                type string;
            }
        }
        container get-voltage {
            leaf voltage {
                type string;
            }
        }
        container get-current {
            leaf current {
                type string;
            }
        }
        container get-all {
            leaf current {
                type string;
            }
            leaf voltage {
                type string;
            }
            leaf rx-pwr {
                type string;
            }
            leaf rx-pwr-dBm {
                type string;
            }
            leaf rx-pwr-type {
                type string;
            }
            leaf tx-pwr {
                type string;
            }
            leaf tx-pwr-dBm {
                type string;
            }
        }
    }
}
